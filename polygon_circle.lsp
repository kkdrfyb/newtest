;poly1这个采用有问题 2023年12月19日
;根据小圆半径和数量画一组环形的相切的圆
(defun C:poly1 (\ pa rr num angle_1 hh brr tmp_circle tmp_point1 small_circle original_circle rotate_angle count)
  (setvar "cmdecho" 0)
  (setq pa (getpoint "\n请输入左下角点"))
  (setq rr (getreal "\n请确定小圆半径"))
  (setq num (getreal "\n请给出小圆的数量"))
  (setq angle_1 (/ 180 num))
  (setq hh (/ rr (/ (sin angle_1) (cos angle_1))))
  (setq brr (sqrt (-(* rr rr) (* hh hh))))
  (setq tmp_point1 (polar pa (/ pi 2) hh))
  (setq cir_center1 (polar tmp_point1 0 rr))
  (command "circle" cir_center1 rr "")
  (setq small_circle (entget (entlast)))
  (setq original_circle (entmake small_circle)) ; 保存原始小圆
  (setq rotate_angle (/ (* 2 pi) num))
  (setq count 1)
  (setq tmp_circle small_circle)
  (while (< count num)
    (command "_.rotate" tmp_circle "" pa rotate_angle)
    ; (command "_.rotate" small_circle "" pa (* (- num count) rotate_angle))
    (setq tmp_circle (entget (entlast)))
    ; (cdr (assoc 10 small_circle))
    (command "circle" (cdr (assoc 10 tmp_circle)) rr)
    (setq count (+ 1 count))
  )
  (princ)
)
;这个有问题，画的圆相交
(defun C:poly(\ pa rr num angle_1 hh brr tmp_point1 tmp_circle)
  (setvar "cmdecho" 0)
  (setq pa (getpoint "\n请输入圆心点"))
  (setq rr (getreal "\n请确定小圆半径"))
  (setq num (getreal "\n请给出小圆的数量"))
  (setq angle_1 (/ 180 num))
  (setq hh (/ rr (/ (sin angle_1) (cos angle_1))))
  (setq brr (sqrt (+ (* rr rr) (* hh hh))))
  (setq tmp_point1 (polar pa (/ pi 2) hh))
  (setq cir_center1 (polar tmp_point1 0 rr))
  (command "circle" cir_center1 rr "")
  (command "array" (entlast) "" "po" pa num 360 "y")
  (princ)
)

;书上的源码
(defun c:poly_book()
  ;以下baspt、rad、num值需由用户输入
  (setq baspt (getpoint "请求输入基准点："))
  (setq rad (getdist baspt "\n请求输入小圆的半径:"))
  (setq num (getint "\n请求输入相切的小圆数量:"))
  ;只要能求得大圆的圆的圆心，再以array命令配合可以了
  ;以下ang1\kk\cenpt值根据程序依据baspt\rad\num求出
  (setq ang1 (/ pi num))
  (setq kk (/ rad (sin ang1)))
  (setq ang2 (- (/ pi 2) ang1))
  (setq cenpt(polar baspt ang2 kk))
  ;以下根据cenpt、num配合环形array画出多圆相切
  (command "circle" baspt rad)
  (command "array" (entlast) "" "p" cenpt num 360 "Y")
  (prin1)
)
