(defun c:zs () 
  (command "zoom" "0.8x")
  (prin1)
)
(defun c:zz () 
  (command "zoom" "1.25x")
  (prin1)
)
(defun c:za () 
  (command "zoom" all)
  (prin1)
)
(defun c:zs () 
  (command "zoom" "e")
  (prin1)
)
(prompt "直接输入0、15、30、45、60、75 十字光标轴线调整值")
;这句没有实现，需要补充
(prin1)
